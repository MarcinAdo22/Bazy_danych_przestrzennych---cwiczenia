FME workspace fme_rasters.fmw

Parameters:
- SourceDataset_GEOTIFF = ""$(FME_MF_DIR)ras250_gb (1)\ras250_gb\data\TM.tif" "$(FME_MF_DIR)ras250_gb (1)\ras250_gb\data\TQ.tif" "$(FME_MF_DIR)ras250_gb (1)\ras250_gb\data\TR.tif" "$(FME_MF_DIR)ras250_gb (1)\ras250_gb\data\TV.tif" "$(FME_MF_DIR)ras250_gb (1)\ras250_gb\data\SK.tif" "$(FME_MF_DIR)ras250_gb (1)\ras250_gb\data\SM.tif" "$(FME_MF_DIR)ras250_gb (1)\ras250_gb\data\SN.tif" "$(FME_MF_DIR)ras250_gb (1)\ras250_gb\data\SO.tif" "$(FME_MF_DIR)ras250_gb (1)\ras250_gb\data\SP.tif" "$(FME_MF_DIR)ras250_gb (1)\ras250_gb\data\SR.tif" "$(FME_MF_DIR)ras250_gb (1)\ras250_gb\data\SS.tif" "$(FME_MF_DIR)ras250_gb (1)\ras250_gb\data\ST.tif" "$(FME_MF_DIR)ras250_gb (1)\ras250_gb\data\SU.tif" "$(FME_MF_DIR)ras250_gb (1)\ras250_gb\data\SV.tif" "$(FME_MF_DIR)ras250_gb (1)\ras250_gb\data\SW.tif" "$(FME_MF_DIR)ras250_gb (1)\ras250_gb\data\SX.tif" "$(FME_MF_DIR)ras250_gb (1)\ras250_gb\data\SY.tif" "$(FME_MF_DIR)ras250_gb (1)\ras250_gb\data\SZ.tif" "$(FME_MF_DIR)ras250_gb (1)\ras250_gb\data\TA.tif" "$(FME_MF_DIR)ras250_gb (1)\ras250_gb\data\TF.tif" "$(FME_MF_DIR)ras250_gb (1)\ras250_gb\data\TG.tif" "$(FME_MF_DIR)ras250_gb (1)\ras250_gb\data\TL.tif" "$(FME_MF_DIR)ras250_gb (1)\ras250_gb\data\NM.tif" "$(FME_MF_DIR)ras250_gb (1)\ras250_gb\data\NN.tif" "$(FME_MF_DIR)ras250_gb (1)\ras250_gb\data\NO.tif" "$(FME_MF_DIR)ras250_gb (1)\ras250_gb\data\NR.tif" "$(FME_MF_DIR)ras250_gb (1)\ras250_gb\data\NS.tif" "$(FME_MF_DIR)ras250_gb (1)\ras250_gb\data\NT.tif" "$(FME_MF_DIR)ras250_gb (1)\ras250_gb\data\NU.tif" "$(FME_MF_DIR)ras250_gb (1)\ras250_gb\data\NW.tif" "$(FME_MF_DIR)ras250_gb (1)\ras250_gb\data\NX.tif" "$(FME_MF_DIR)ras250_gb (1)\ras250_gb\data\NY.tif" "$(FME_MF_DIR)ras250_gb (1)\ras250_gb\data\NZ.tif" "$(FME_MF_DIR)ras250_gb (1)\ras250_gb\data\OV.tif" "$(FME_MF_DIR)ras250_gb (1)\ras250_gb\data\SC.tif" "$(FME_MF_DIR)ras250_gb (1)\ras250_gb\data\SD.tif" "$(FME_MF_DIR)ras250_gb (1)\ras250_gb\data\SE.tif" "$(FME_MF_DIR)ras250_gb (1)\ras250_gb\data\SH.tif" "$(FME_MF_DIR)ras250_gb (1)\ras250_gb\data\SJ.tif" "$(FME_MF_DIR)ras250_gb (1)\ras250_gb\data\HP.tif" "$(FME_MF_DIR)ras250_gb (1)\ras250_gb\data\HT.tif" "$(FME_MF_DIR)ras250_gb (1)\ras250_gb\data\HU.tif" "$(FME_MF_DIR)ras250_gb (1)\ras250_gb\data\HW.tif" "$(FME_MF_DIR)ras250_gb (1)\ras250_gb\data\HX.tif" "$(FME_MF_DIR)ras250_gb (1)\ras250_gb\data\HY.tif" "$(FME_MF_DIR)ras250_gb (1)\ras250_gb\data\HZ.tif" "$(FME_MF_DIR)ras250_gb (1)\ras250_gb\data\NA.tif" "$(FME_MF_DIR)ras250_gb (1)\ras250_gb\data\NB.tif" "$(FME_MF_DIR)ras250_gb (1)\ras250_gb\data\NC.tif" "$(FME_MF_DIR)ras250_gb (1)\ras250_gb\data\ND.tif" "$(FME_MF_DIR)ras250_gb (1)\ras250_gb\data\NF.tif" "$(FME_MF_DIR)ras250_gb (1)\ras250_gb\data\NG.tif" "$(FME_MF_DIR)ras250_gb (1)\ras250_gb\data\NH.tif" "$(FME_MF_DIR)ras250_gb (1)\ras250_gb\data\NJ.tif" "$(FME_MF_DIR)ras250_gb (1)\ras250_gb\data\NK.tif" "$(FME_MF_DIR)ras250_gb (1)\ras250_gb\data\NL.tif""   # Source GeoTIFF File(s) or URL(s)
- SourceDataset_GEOTIFF_3 = $(FME_MF_DIR)ras250_gb (1)\ras250_gb\data\SN.tif   # Source GeoTIFF File(s) or URL(s)
- DestDataset_FILEGDB = $(FME_MF_DIR)Results.gdb   # File Geodatabase
- SourceDataset_SHAPEFILE_3 = $(FME_MF_DIR)bdline_essh_gb\Data\GB\scotland_and_wales_region.shp   # Source Esri Shapefile(s)
- DestDataset_POSTGIS_RASTER_3 = postgis_rast   # Connection

Readers:
- GEOTIFF_1: GEOTIFF from $(SourceDataset_GEOTIFF) in EPSG:4326
- GEOTIFF_2: GEOTIFF from $(SourceDataset_GEOTIFF_3) in EPSG4326
- SHAPEFILE_2: SHAPEFILE from $(SourceDataset_SHAPEFILE_3)

Writers:
- FILEGDB_1: FILEGDB to $(DestDataset_FILEGDB) in EPSG:4326
- POSTGIS_RASTER_2: POSTGIS_RASTER to $(DestDataset_POSTGIS_RASTER_3)

scotland_and_wales_region (reader SHAPEFILE_2)
    attributes: NAME varchar(100), AREA_CODE varchar(3), DESCRIPTIO varchar(50), FILE_NAME varchar(100), NUMBER number(11,0), NUMBER0 number(11,0), POLYGON_ID number(11,0), UNIT_ID number(11,0), CODE varchar(9), HECTARES float, AREA float, TYPE_CODE varchar(2), DESCRIPT0 varchar(25), TYPE_COD0 varchar(3), DESCRIPT1 varchar(36)
    -> TestFilter
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(NAME) BEGINS_WITH South Wales",@Value(NAME) BEGINS_WITH South Wales
    @Value(NAME) BEGINS_WITH South Wales -> Inspector_5
    @Value(NAME) BEGINS_WITH South Wales -> Clipper [CLIPPER]
Inspector_5
GEOTIFF (reader GEOTIFF_2)
    -> FilePathExtractor [Initiator]
FilePathExtractor
    EXTRACT_ARCHIVES = Yes
    SOURCE_DATASET = ""$(FME_MF_DIR)ras250_gb (1)\ras250_gb\data\TM.tif" "$(FME_MF_DIR)ras250_gb (1)\ras250_gb\data\TQ.tif" "$(FME_MF_DIR)ras250_gb (1)\ras250_gb\data\TR.tif" "$(FME_MF_DIR)ras250_gb (1)\ras250_gb\data\TV.tif" "$(FME_MF_DIR)ras250_gb (1)\ras250_gb\data\SK.tif" "$(FME_MF_DIR)ras250_gb (1)\ras250_gb\data\SM.tif" "$(FME_MF_DIR)ras250_gb (1)\ras250_gb\data\SN.tif" "$(FME_MF_DIR)ras250_gb (1)\ras250_gb\data\SO.tif" "$(FME_MF_DIR)ras250_gb (1)\ras250_gb\data\SP.tif" "$(FME_MF_DIR)ras250_gb (1)\ras250_gb\data\SR.tif" "$(FME_MF_DIR)ras250_gb (1)\ras250_gb\data\SS.tif" "$(FME_MF_DIR)ras250_gb (1)\ras250_gb\data\ST.tif" "$(FME_MF_DIR)ras250_gb (1)\ras250_gb\data\SU.tif" "$(FME_MF_DIR)ras250_gb (1)\ras250_gb\data\SV.tif" "$(FME_MF_DIR)ras250_gb (1)\ras250_gb\data\SW.tif" "$(FME_MF_DIR)ras250_gb (1)\ras250_gb\data\SX.tif" "$(FME_MF_DIR)ras250_gb (1)\ras250_gb\data\SY.tif" "$(FME_MF_DIR)ras250_gb (1)\ras250_gb\data\SZ.tif" "$(FME_MF_DIR)ras250_gb (1)\ras250_gb\data\TA.tif" "$(FME_MF_DIR)ras250_gb (1)\ras250_gb\data\TF.tif" "$(FME_MF_DIR)ras250_gb (1)\ras250_gb\data\TG.tif" "$(FME_MF_DIR)ras250_gb (1)\ras250_gb\data\TL.tif" "$(FME_MF_DIR)ras250_gb (1)\ras250_gb\data\NM.tif" "$(FME_MF_DIR)ras250_gb (1)\ras250_gb\data\NN.tif" "$(FME_MF_DIR)ras250_gb (1)\ras250_gb\data\NO.tif" "$(FME_MF_DIR)ras250_gb (1)\ras250_gb\data\NR.tif" "$(FME_MF_DIR)ras250_gb (1)\ras250_gb\data\NS.tif" "$(FME_MF_DIR)ras250_gb (1)\ras250_gb\data\NT.tif" "$(FME_MF_DIR)ras250_gb (1)\ras250_gb\data\NU.tif" "$(FME_MF_DIR)ras250_gb (1)\ras250_gb\data\NW.tif" "$(FME_MF_DIR)ras250_gb (1)\ras250_gb\data\NX.tif" "$(FME_MF_DIR)ras250_gb (1)\ras250_gb\data\NY.tif" "$(FME_MF_DIR)ras250_gb (1)\ras250_gb\data\NZ.tif" "$(FME_MF_DIR)ras250_gb (1)\ras250_gb\data\OV.tif" "$(FME_MF_DIR)ras250_gb (1)\ras250_gb\data\SC.tif" "$(FME_MF_DIR)ras250_gb (1)\ras250_gb\data\SD.tif" "$(FME_MF_DIR)ras250_gb (1)\ras250_gb\data\SE.tif" "$(FME_MF_DIR)ras250_gb (1)\ras250_gb\data\SH.tif" "$(FME_MF_DIR)ras250_gb (1)\ras250_gb\data\SJ.tif" "$(FME_MF_DIR)ras250_gb (1)\ras250_gb\data\HP.tif" "$(FME_MF_DIR)ras250_gb (1)\ras250_gb\data\HT.tif" "$(FME_MF_DIR)ras250_gb (1)\ras250_gb\data\HU.tif" "$(FME_MF_DIR)ras250_gb (1)\ras250_gb\data\HW.tif" "$(FME_MF_DIR)ras250_gb (1)\ras250_gb\data\HX.tif" "$(FME_MF_DIR)ras250_gb (1)\ras250_gb\data\HY.tif" "$(FME_MF_DIR)ras250_gb (1)\ras250_gb\data\HZ.tif" "$(FME_MF_DIR)ras250_gb (1)\ras250_gb\data\NA.tif" "$(FME_MF_DIR)ras250_gb (1)\ras250_gb\data\NB.tif" "$(FME_MF_DIR)ras250_gb (1)\ras250_gb\data\NC.tif" "$(FME_MF_DIR)ras250_gb (1)\ras250_gb\data\ND.tif" "$(FME_MF_DIR)ras250_gb (1)\ras250_gb\data\NF.tif" "$(FME_MF_DIR)ras250_gb (1)\ras250_gb\data\NG.tif" "$(FME_MF_DIR)ras250_gb (1)\ras250_gb\data\NH.tif" "$(FME_MF_DIR)ras250_gb (1)\ras250_gb\data\NJ.tif" "$(FME_MF_DIR)ras250_gb (1)\ras250_gb\data\NK.tif" "$(FME_MF_DIR)ras250_gb (1)\ras250_gb\data\NL.tif""
    -> Inspector_4
    -> FilePropertyExtractor
FilePropertyExtractor
    FMT = FME Date/Time (%Y%m%d%H%M%S)
    PATH = @Value(_path_windows)
    -> Inspector_2
    -> JoinAttributesbyFieldValue [Supplier]
Inspector_2
Inspector_4
GEOTIFF (reader GEOTIFF_1)
    -> RasterExtentsCoercer
    -> JoinAttributesbyFieldValue [Requestor]
    -> RasterPaletteResolver
RasterExtentsCoercer
    EXTENTS_TYPE = Raster Extents
    EXTENTS -> Inspector
Inspector
JoinAttributesbyFieldValue
    IDD = @Value(fme_basename)
    col1 = @Value(fme_basename)
    jtype = one-to-one
    operator = Contains
    Merged -> AttributeCreator
AttributeCreator
    ATTR_TABLE = SET_TO NewName (varchar(200)) = @Value(fme_basename)_@Value(_file_size)
    -> Inspector_3
    -> Extents (writer FILEGDB_1)
Inspector_3
Extents (writer FILEGDB_1)
RasterPaletteResolver
    -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Inspector_6
    INSIDE -> Exports (writer POSTGIS_RASTER_2)
Inspector_6
Exports (writer POSTGIS_RASTER_2)
    attributes: geotiff_type varchar(255), _clipped char(3)

FME custom transformer FilePathExtractor
Extracts all the file paths which can be accessed by a string specified through a Filename (Multiple) type user parameter, and outputs features each of which has attributes storing the file path, file name, directory path etc.  
If the source string contains a zip or 7-Zip file path which is specified with the Select Multiple Folders/Files function (called "Advanced Browser" in the old days), the transformer considers it as a folder-like thing, will extact it automatically and output features for each extracted file.  
A zip or a 7z file directly specified with the standard Select Files dialog will also be extracted by default. However, you can set No to the Extract Archives parameter not to extract them.
Parameters
Source Dataset
Extract Archives

Parameters:
- SOURCE_DATASET =   # Source Dataset
- EXTRACT_ARCHIVES = Yes   # Extract Archives

Initiator (input)
    -> ParameterFetcher
ParameterFetcher
    ATTR_LIST = __source_dataset $(SOURCE_DATASET)
    -> PythonCaller
PythonCaller
    HIDE_ATTRIBUTES = __source_dataset
    NEW_ATTRIBUTES = __path_unix
    PYTHONSOURCE:
      import fme
      import fmeobjects
      import shlex
      class PathElementExtractor(object):
          def __init__(self):
              pass

          def input(self, feature):
              dataset = feature.getAttribute('__source_dataset').replace('\\', '/')
              feature.removeAttribute('__source_dataset')
              if dataset.startswith('"'):
                  for path in shlex.split(dataset.replace('""', '"')):
                      feature.setAttribute('__path_unix', path)
                      self.pyoutput(feature)
              else:
                  feature.setAttribute('__path_unix', dataset)
                  self.pyoutput(feature)

          def close(self):
              pass
    PYTHONSYMBOL = PathElementExtractor
    -> StringSearcher
Note: ^(.+\.(zip|7z|7zip))\[(.+)\]$
StringSearcher
    CASE = no
    MATCHED_PARTS_ATTR = _sub
    REGEXP = ^(.+\.(zip|7z|7zip))\[(.+)\]$
    STRING_TO_SEARCH = @Value(__path_unix)
    MATCHED -> AttributeManager
    NOT_MATCHED -> AttributeCreator
AttributeManager
    ATTR_TABLE:
      SET_TO __dirpath = FME_CONDITIONAL:DEFAULT_VALUE'@Value(_sub{0}.part)'BOOL_OP;OR;COMPOSITE_TEST;1;CASE_INSENSITIVE_TEST @Value(_sub{1}.part) BEGINS_WITH **/'@Value(_sub{0}.part)/**/'FME_NUM_CONDITIONS2___
      SET_TO __recurse_into_subfolders = FME_CONDITIONAL:DEFAULT_VALUE'No'BOOL_OP;OR;COMPOSITE_TEST;1;CASE_INSENSITIVE_TEST @Value(_sub{2}.part) BEGINS_WITH **/'Yes'FME_NUM_CONDITIONS2___
      SET_TO __path_filter = @ReplaceRegEx(@Value(_sub{2}.part),"(\*\*/)?(.+)",\2)
      SET_TO __dirpath = @Value(_sub{0}.part)
      SET_TO
      REMOVE __path_unix
      REMOVE _sub{}.part
      REMOVE _sub{}.startIndex
    -> FeatureReader [INITIATOR]
AttributeCreator
    ATTR_TABLE = SET_TO __recurse_into_subfolders = No
    -> FilenamePartExtractor
FilenamePartExtractor
    DIRPATH_ATTR = __dirpath
    FULLNAME_ATTR = __path_filter
    SRC_ATTR = @Value(__path_unix)
    -> FeatureReader [INITIATOR]
FeatureReader
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Merge Initiator and Result
    ATTR_CONFLICT_RES = Use Result
    COMBINE_GEOM = Use Initiator
    DATASET = @Value(__dirpath)
    FORMAT = PATH
    OUTPUT_FEATURES_DISPLAY = Data Features
    PATH_GLOB_PATTERN = @Value(__path_filter)
    PATH_NO_EMPTY_PROPERTIES = YES
    PATH_RECURSE_DIRECTORIES = @Value(__recurse_into_subfolders)
    PATH_RETRIEVE_FILE_PROPERTIES = NO
    PATH_TYPE = FILE
    PATH -> Tester
Tester
    BOOL_OP = COMPOSITE
    COMPOSITE_TEST = 1 AND 2
    TEST_CLAUSE:
      CASE_INSENSITIVE_TEST @Value(path_extension) IN zip,7z,7zip
      CASE_INSENSITIVE_TEST $(EXTRACT_ARCHIVES) = Yes
    TEST_MODE = CASE_INSENSITIVE_TEST
    PASSED -> FeatureReader_2 [INITIATOR]
    FAILED -> AttributeManager_2
Note: Extract archives.
FeatureReader_2
    ATTRIBUTES = PATH,"path_unix,path_windows,path_rootname,path_filename,path_extension,path_filesize,path_ownername,path_readonly,path_modified_date,path_created_date,path_accessed_date,path_directory_unix,path_directory_windows,path_type,fme_geometry{0}"
    ATTR_ACCUM_MODE = Merge Initiator and Result
    ATTR_CONFLICT_RES = Use Result
    COMBINE_GEOM = Use Initiator
    DATASET = @Value(path_unix)
    FORMAT = PATH
    OUTPUT_FEATURES_DISPLAY = Data Features
    PATH_GLOB_PATTERN = *
    PATH_NO_EMPTY_PROPERTIES = YES
    PATH_RECURSE_DIRECTORIES = YES
    PATH_RETRIEVE_FILE_PROPERTIES = NO
    PATH_TYPE = FILE
    PATH -> AttributeManager_2
AttributeManager_2
    ATTR_TABLE:
      RENAME_SET_VALUE path_unix > _path_unix
      RENAME_SET_VALUE path_windows > _path_windows
      RENAME_SET_VALUE path_filename > _path_filename
      RENAME_SET_VALUE path_rootname > _path_rootname
      RENAME_SET_VALUE path_extension > _path_extension
      RENAME_SET_VALUE path_directory_unix > _path_directory_unix
      RENAME_SET_VALUE path_directory_windows > _path_directory_windows
      REMOVE __path_unix
      REMOVE __dirpath
      REMOVE __path_filter
      REMOVE path_filesize
      REMOVE path_ownername
      REMOVE path_readonly
      REMOVE path_modified_date
      REMOVE path_created_date
      REMOVE path_accessed_date
      REMOVE path_type
      REMOVE fme_geometry{}
      REMOVE __recurse_into_subfolders
      REMOVE fme_geometry{0}
    -> Output (output)
Output (output)

FME custom transformer FilePropertyExtractor
Extracts basic properties of a file or a directory and adds these attributes to the feature.
    _file_type
    : holds "File" or "Directory", which indicates whether the specified path is a file or a directory.
    _file_size
    : holds the size of file/directory in bytes (total of file sizes if directory)
    _file_atime
    : holds the time of last access.
    _file_mtime
    : holds the time of last modification.
    _file_ctime
    : holds the time of creation on some systems (like Windows), or the time of last metadata change on other systems (like Unix).
    You can specify the format of "_file_atime", "_file_mtime", and "_file_ctime" via the "Date/Time Format" parameter.
    The input feature will be output from the 
    <Rejected>
    port if the specified file/directory does not exist, the path indicates a symbolic link, or an unexpected error has occurred. 
    This transformer contains a Python script, which was tested with both Python 2.7 and Python 3.4 interpreter.
Parameters
    File/Directory Path
    :
    Specify the path of a file or a directory.
    Date/Time Format
    :
    Specify a date/datetime/time format that should be applied to the values of "_file_atime", "_file_mtime", and "_file_ctime". 
    The format syntax is the same as the DateFormatter. See the help doc on the transformer.

Parameters:
- PATH =   # File/Directory Path
- FMT = FME Date/Time (%Y%m%d%H%M%S)

Input (input)
    -> ParameterFetcher
ParameterFetcher
    ATTR_LIST = __filepropertyextractor.path {$(PATH)}
    -> PythonCaller
PythonCaller
    NEW_ATTRIBUTES = _file_type _file_size _file_atime _file_mtime _file_ctime __filepropertyextractor.error
    PYTHONSOURCE:
      # 2016-05-25, Takashi Iijima, Original Implementation
      # 2020-01-28, Takashi Iijima, Calculate Directory Size as Total File Sizes under the Directory; Changed Default Python Interpreter to 3.6+

      import fme, fmeobjects
      import os
      def extractFileProperty(feature):
          def get_dir_size(path):
              total = 0
              for p in os.listdir(path):
                  full_path = os.path.join(path, p)
                  if os.path.isfile(full_path):
                      total += os.path.getsize(full_path)
                  elif os.path.isdir(full_path):
                      total += get_dir_size(full_path)
              return total
          try:
              path = feature.getAttribute('__filepropertyextractor.path')
              if os.path.exists(path) and not os.path.islink(path):
                  s = os.stat(path)
                  if os.path.isdir(path):
                      feature.setAttribute('_file_type', 'Directory')
                      feature.setAttribute('_file_size', get_dir_size(path))
                  else:
                      feature.setAttribute('_file_type', 'File')
                      feature.setAttribute('_file_size', s.st_size)
                  feature.setAttribute('_file_atime', int(s.st_atime))
                  feature.setAttribute('_file_mtime', int(s.st_mtime))
                  feature.setAttribute('_file_ctime', int(s.st_ctime))
              else:
                  raise Exception('specified file/directory does not exist')
          except Exception as ex:
              feature.setAttribute('__filepropertyextractor.error', '%s' % ex)
    PYTHONSYMBOL = extractFileProperty
    -> Tester
Tester
    BOOL_OP = OR
    TEST_CLAUSE = TEST __filepropertyextractor.error ATTRIBUTE_IS_MISSING ""
    TEST_MODE = Automatic
    PASSED -> AttributeRemover
    FAILED -> AttributeRemover_2
AttributeRemover
    REMOVE_ATTRS = __filepropertyextractor.path,__filepropertyextractor.error
    -> DateFormatter
DateFormatter
    DATE_ATTR = _file_ctime,_file_mtime,_file_atime
    FMT = $(FMT)
    INVALID_DATE_VALUE = _FME_NO_OP_
    SRCFMT = %s
    -> Output (output)
Output (output)
AttributeRemover_2
    REMOVE_ATTRS = _file_size,_file_type,_file_ctime,__filepropertyextractor.path,_file_mtime,_file_atime
    -> AttributeRenamer
AttributeRenamer
    ATTR_TABLE = RENAME_SET_DEFAULT __filepropertyextractor.error > _rejected_reason
    -> <Rejected> (output)
<Rejected> (output)
